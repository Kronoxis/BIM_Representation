FME workspace IFCConverter.fmw

Parameters:
- InputFiles = ""E:\School\3DAE4\Semester 5\Graduation Work\Repository\Interactive_BIM\Files\Clinic\Clinic_A.ifc" "E:\School\3DAE4\Semester 5\Graduation Work\Repository\Interactive_BIM\Files\Clinic\Clinic_MEP.ifc" "E:\School\3DAE4\Semester 5\Graduation Work\Repository\Interactive_BIM\Files\Clinic\Clinic_S.ifc""   # IFC File(s)
- OutputFolder = E:\School\3DAE4\Semester 5\Graduation Work\Repository\Interactive_BIM\Files\Clinic   # Output Folder
- OutputName = Clinic   # Output File Name
- Output_CenterPoints = $(OutputFolder)   # CenterPoints Destination
- Output_FBX = $(OutputFolder)   # FBX Destination

Readers:
- IFC_1: IFC from $(InputFiles)
- IFC_2: IFC from $(InputFiles)

Writers:
- FBX_1: FBX to $(Output_FBX)
- CSV2_1: CSV2 to $(Output_CenterPoints)

PropertySetDefinition (reader IFC_2)
    attributes: CompositionType enumeration, BuildingAddress.PostalBox string, ElevationOfTerrain real, BuildingAddress.Purpose enumeration, NumberOfTreads int, ifc_properties{}.data_type string, SiteAddress.Town string, BuildingAddress.InternalLocation string, ObjectType string, SiteAddress.Purpose enumeration, LongName string, InteriorOrExteriorSpace enumeration, SiteAddress.UserDefinedPurpose string, BuildingAddress.Town string, ElevationWithFlooring real, Elevation real, Name string, ifc_properties{}.name string, SiteAddress.Region string, BuildingAddress.Region string, RefLatitude real, ifc_property_set_name string, OverallHeight real, RiserHeight real, ElevationOfRefHeight real, PredefinedType enumeration, BuildingAddress.AddressLines string, BuildingAddress.UserDefinedPurpose string, TreadLength real, BuildingAddress.Description string,
      BuildingAddress.PostalCode string, SiteAddress.InternalLocation string, SiteAddress.Country string, SiteAddress.Description string, RefElevation real, NumberOfRiser int, RefLongitude real, ifc_properties{}.property_type string, SiteAddress.AddressLines string, LandTitleNumber string, Tag string, SiteAddress.PostalCode string, BuildingAddress.Country string, GlobalId char(22), ShapeType enumeration, OverallWidth real, Description string, Phase string, SiteAddress.PostalBox string
    -> SetGeomName
SetGeomName: GeometryPropertySetter
    OVERWRITE_CHOICE = Yes
    SETTYPE_PARAM = Geometry Name
    GEOM_NAME_FIELD = '@Substring(@Value(Name),0,@FindString(@Value(Name),":"))',@Value(Tag),@Value(fme_feature_type)
    SET -> Hold_Until_Done
Hold_Until_Done: FeatureHolder
    -> FeatureMerger [REQUESTOR]
    -> Expose_Geometry_Type

Bookmark: Set Scale From Project's Length Unit, Extract geometry (FBX)
IfcProject (reader IFC_1)
    attributes: GlobalId char(22), Name string, Description string, ObjectType string, LongName string, Phase string, ifc_quantity_set{} string, ifc_property_set{} string
    -> Expose_Lengthunit
Expose_Lengthunit: AttributeExposer
    ATTR_LIST = lengthunit
    -> StringPairReplacer
StringPairReplacer
    CASE = no
    RESULT_ATTR = scale
    SRC_ATTR = lengthunit
    MAP = kilometre 100000 hectometre 10000 decametre 1000 metre 100 decimetre 10 centimetre 1 millimetre 0.1
    -> FeatureMerger [SUPPLIER]
FeatureMerger
    ATTR_ACCUM_MODE = Merge Supplier
    MERGE_TYPE = Attributes Only
    SUPPLIERS_FIRST = Yes
    IGNORE_NULLS = No
    CONNECT_Z_MODE = First Wins
    JOIN_KEYS = $(InputFiles) $(InputFiles) AUTO
    PROCESS_DUPS = Yes
    REJECT_NULL_MISSING_KEYS = No
    ATTR_CONFLICT_RES = Use Requestor
    GEOM_TYPE = Build Polygons
    MERGED -> Scale_Geometry
Scale_Geometry: Scaler
    RASTER_SCALING = Extents
    SCALE_ORIGIN = 0,0
    XSCALE = @Value(scale)
    TEXT_LOC_ONLY = Location and Size
    ZSCALE = @Value(scale)
    YSCALE = @Value(scale)
    SCALED -> Duplex (writer FBX_1)
Duplex (writer FBX_1)

Bookmark: Extract Door Pivot Properties (CSV)
Expose_Geometry_Type: AttributeExposer
    ATTR_LIST = fme_geometry,fme_type
    -> Deaggregator
Deaggregator
    MODE = Flatten All Levels
    SPLIT_COMPOSITES = No
    LIST_ATTR_MODE_LOOKUP = LEAN
    GEOM_NAME_FIELD = Deaggregated
    EXPLODE_INSTANCES = No
    DEAGGREGATED -> CopyType
CopyType: AttributeCopier
    ATTR_TABLE = COPY fme_feature_type > Type
    -> Test_Arc
Test_Arc: Tester
    BOOL_OP = AND
    TEST_DESCRIPTION = Is Arc
    TEST_MODE = Automatic
    TEST_CLAUSE = TEST @Value(fme_type) = fme_arc
    PASSED -> ArcExtractor
ArcExtractor: ArcPropertyExtractor
    SEC_RADIUS = Radius2
    END_Y = EndY
    CENTER_X = CenterX
    START_Y = StartY
    ROTATION = Rotation
    START_X = StartX
    END_Z = EndZ
    END_X = EndX
    SWEEP_ANGLE = SweepAngle
    START_Z = StartZ
    PRIM_RADIUS = Radius1
    START_ANGLE = StartAngle
    CENTER_Y = CenterY
    CENTER_Z = CenterZ
    -> Test_Door
Test_Door: Tester
    BOOL_OP = OR
    TEST_DESCRIPTION = ""
    TEST_MODE = Automatic
    TEST_CLAUSE = TEST @Value(fme_feature_type) = IfcDoor
    PASSED -> DoorProperties (writer CSV2_1)
DoorProperties (writer CSV2_1)
    attributes: Name string, Type string, Tag string, Rotation real32, StartAngle real32, SweepAngle real32, CenterX x_coordinate, CenterY y_coordinate, CenterZ z_coordinate

FME custom transformer WorkspacePauser
This transformer allows to pause a workspace at any specific place in the process. Just connect any transformer/reader to this transformer and set the puasing time (in seconds).
Pausing Time in Seconds.

Parameters:
- Pauser = 10   # Pausing time (Seconds)

Input (input)
    -> Counter
Counter
    START = 0
    SCOPE = Local
    DOMAIN = counterPause
    CNT_ATTR = _count
    -> PythonCaller
PythonCaller
    PYTHONSOURCE:
      import fme
      import fmeobjects
      import time

      # Template Function interface:
      # When using this function, make sure its name is set as the value of
      # the 'Class or Function to Process Features' transformer parameter

      def processFeature(feature):

           PauseTime = $(Pauser)
           Break = feature.getAttribute('_count')
           if int(Break) == 0:
              time.sleep(int(PauseTime))
           else:

              pass
    PYTHONSYMBOL = processFeature
